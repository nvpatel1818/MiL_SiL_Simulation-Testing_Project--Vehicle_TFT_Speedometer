# TFT_Cluster_Speedometer_Req_1818

## SwReq_TFT_Cluster_Speedometer_01 (Functional)
Calculating TFT Display Speed
Average vehicle speed would be displaying if its between 2 kmph to 250 kmph. Any value outside this range will be discarded by upper and lower limits.
When Average Vehicle speed is between 2 kmph & 250 kmph, Display Speed= Average Vehicle Speed.
When Average vehicle speed >250 kmph, Display speed= 250 kmph

## SwReq_TFT_Cluster_Speedometer_02 (Functional)
Main Data Filtering
Main data filtering subsystem will be activated for every 10th milliseconds
DisplaySpeed1 (t)= ((DisplaySpeed (t)*0.65)/ Main Filter Speed value)- 0.05

## SwReq_TFT_Cluster_Speedometer_03 (Functional)
Auxilliary Data Filtering
Auxilliary data filtering subsystem will be activated for every 10th milliseconds
DisplaySpeed_Filter (t)= ((DisplaySpeed1 (t)*0.78)/ auxilliary filter speed value)-0.03

## SwReq_TFT_Cluster_Speedometer_04 (Functional)
| TFT Speed Output if (DisplaySpeedFilter - DisplaySpeed)\| > 1.5 |
| --- |
| { |
| Vehicle Speed Display = DisplaySpeed |
| } |
| else |
| { |
| Vehicle Speed Display = DisplaySpeed Filter |
| } |
